from PySide import QtGui

reply = QtGui.QInputDialog.getText(None, "Ouija Central","Enter your thoughts for the day:")
if reply[1]:
	# user clicked OK
	replyText = reply[0]
	QtGui.QMessageBox.question(None, "Entered:", "you entered: " + reply[0],
         QtGui.QMessageBox.Yes | QtGui.QMessageBox.No, QtGui.QMessageBox.No)
	#print("you entered",reply[0])
else:
	# user clicked Cancel
	replyText = reply[0] # which will be "" if they clicked Cancel
