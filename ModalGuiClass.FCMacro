from PySide import QtGui, QtCore

class ExampleModalGuiClass(QtGui.QDialog):

	def __init__(self):
		super(ExampleModalGuiClass, self).__init__()
		self.initUI()
	def initUI(self):
		#print("asdf")		
		self.result = userCancelled
		self.setGeometry(250,250,400,330)
		self.setWindowTitle("Our example program window")
		self.setWindowFlags(QtCore.Qt.WindowStaysOnTopHint)

		self.label1 = QtGui.QLabel("                       ",self)
		self.label1.setFont('Courier')
		self.label1.move(20,20)

		self.label2 = QtGui.QLabel("sample string No. two",self)
		self.label2.move(20,70)

		self.label3 = QtGui.QLabel("                       ",self)
		self.label3.setFont('Courier')
		self.label3.move(20,120)

		self.label4 = QtGui.QLabel("can you see this?",self)
		self.label4.move(20,170)

		self.checkbox1 = QtGui.QCheckBox("Left side",self)
		self.checkbox1.clicked.connect(self.onCheckbox1)
		#self.checkbox1.toggle() #will set if executed
		self.checkbox1.move(210,10)
		
		self.checkbox2 = QtGui.QCheckBox("Right side",self)
		self.checkbox2.clicked.connect(self.onCheckbox2)
		self.checkbox2.move(210,30)
		
		self.radioButton1 = QtGui.QRadioButton("random string one",self)
		self.radioButton1.clicked.connect(self.onRadioButton1)
		self.radioButton1.move(210,60)

		self.radioButton2 = QtGui.QRadioButton("owt gnirts modnar",self)
		self.radioButton2.clicked.connect(self.onRadioButton2)
		self.radioButton2.move(210,80)

		self.popupItems1 = ("pizza","apples","candy","cake","potatoes")
		self.popup1 = QtGui.QComboBox(self)
		self.popup1.addItems(self.popupItems1)
		self.popup1.setCurrentIndex(self.popupItems1.index("candy"))
		self.popup1.activated[str].connect(self.onPopup1)
		self.popup1.move(210, 115)

		pushButton1 = QtGui.QPushButton('Toggle visibility', self)
		pushButton1.clicked.connect(self.onPushButton1)
		pushButton1.setAutoDefault(False)
		pushButton1.move(210, 165)

		self.textInput = QtGui.QLineEdit(self)
		self.textInput.setText("cats & dogs")
		self.textInput.setFixedWidth(190)
		self.textInput.move(20, 220)

		popMenuAction1 = QtGui.QAction(self)
		popMenuAction1.setText("load some text")
		popMenuAction1.triggered.connect(self.onPopMenuAction1)

		popMenuAction2 = QtGui.QAction(self)
		popMenuAction2.setText("uppercase")
		popMenuAction2.triggered.connect(self.onPopMenuAction2)

		popMenuDivider = QtGui.QAction(self)
		popMenuDivider.setText('---------')
		popMenuDivider.triggered.connect(self.onPopMenuDivider)

		popMenuAction3 = QtGui.QAction(self)
		popMenuAction3.setText("clear")
		popMenuAction3.triggered.connect(self.onPopMenuAction3)

		self.textInput.setContextMenuPolicy(QtCore.Qt.ActionsContextMenu)
		self.textInput.addAction(popMenuAction1)
		self.textInput.addAction(popMenuAction2)
		self.textInput.addAction(popMenuDivider)
		self.textInput.addAction(popMenuAction3)

		self.numericInput = QtGui.QLineEdit(self)
		self.numericInput.setInputMask("999")
		self.numericInput.setText("000")
		self.numericInput.setFixedWidth(50)
		self.numericInput.move(250, 220)

		cancelButton = QtGui.QPushButton('Cancel', self)
		cancelButton.clicked.connect(self.onCancel)
		cancelButton.setAutoDefault(True)
		cancelButton.move(150, 280)

		okButton = QtGui.QPushButton('OK', self)
		okButton.clicked.connect(self.onOk)
		okButton.move(260, 280)

		self.show()

	def onCheckbox1(self):
		text = self.label1.text()
		if text[0]==' ':
			self.label1.setText('left'+text[4:])
		else:
			self.label1.setText('    '+text[4:])
	def onCheckbox2(self):
		text = self.label1.text()
		if text[-1]==' ':
			self.label1.setText(text[:-5]+'right')
		else:
			self.label1.setText(text[:-5]+'     ')
	def onRadioButton1(self):
		self.label2.setText(self.radioButton1.text())
	def onRadioButton2(self):
		self.label2.setText(self.radioButton2.text())
	def onPopup1(self, selectedText):
		if self.label3.text().isspace():
			self.label3.setText(selectedText)
		else:
			self.label3.setText(self.label3.text()+","+selectedText)
	def onPushButton1(self):
		if self.label4.isVisible():
			self.label4.hide()
		else:
			self.label4.show()
	def onPopMenuAction1(self):
		# load some text into field
		self.textInput.setText("Lorem ipsum dolor sit amet")
	def onPopMenuAction2(self):
		# set text in field to uppercase
		self.textInput.setText(self.textInput.text().upper())
	def onPopMenuDivider(self):
		# this option is the divider and is really there as a spacer on the menu list
		# consequently it has no functional code to execute if user selects it
		pass
	def onPopMenuAction3(self):
		# clear the text from the field
		self.textInput.setText('')
	def onCancel(self):
		self.result			= userCancelled
		self.close()
	def onOk(self):
		self.result			= userOK
		self.close()
	def mousePressEvent(self, event):
		# print mouse position, X & Y
		print ("X = ", event.pos().x())
		print ("Y = ", event.pos().y())
		#
		if event.button() == QtCore.Qt.LeftButton:
			print ("left mouse button")
		if self.label1.underMouse():
			print ("over the text '"+self.label1.text()+"'")
		if self.label2.underMouse():
			print ("over the text '"+self.label2.text()+"'")
		if self.label3.underMouse():
			print ("over the text '"+self.label3.text()+"'")
		if self.label4.underMouse():
			print ("over the text '"+self.label4.text()+"'")
		if self.textInput.underMouse():
			print ("over the text '"+self.textInput.text()+"'")
		if event.button() == QtCore.Qt.RightButton:
			print ("right mouse button")

userCancelled		= "Cancelled"
userOK			= "OK"

		
form = ExampleModalGuiClass()
form.exec_()

if form.result==userCancelled:
	pass # steps to handle user clicking Cancel
if form.result==userOK:
	# steps to handle user clicking OK
	localVariable1 = form.label1.text()
	localVariable2 = form.label2.text()
	localVariable3 = form.label3.text()
	localVariable4 = form.label4.text()
	print (ocalVariable1)
	print (localVariable2)
	print (localVariable3)
	print (localVariable4)
