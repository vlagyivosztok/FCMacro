from math import sqrt
import os

#region követelmények
"""
függvények:
-vire_condition
-horony pontok beszerzése FC-ből
-(később méretek átadása a horony geometriához)
-kör adatai Fc-nek, majd kör kontúrpontjait vissza.

"""


#endregion
#  


def getGrooveContour():
    #elsőre egy kész kontúrt dolgozunk fel, ami már meg van nyitva
	#később átadunk adatokat
	#listben, az első a fajtát határozza meg, a többi a hozzá tartozó adatok
	pass

def PlaceWireCs():
    

	pass

#region main
#globals
#wire d
Dh = 0.8
#insul thkn
Hsz = 0.1
#outer d
Dk = Dh + 2*Hsz
#gap 
Lr =0.05
#basic dist
A = Dk + Lr

# x = 0,a,2a,3a by even y unit
# x= a/2, 3a/2, 5a/2 by odd y unit
# y = sqrt(3)/2 and multiplied by 1,2,3...

x=0
y=0
# y basic incr
y_incr = A*sqrt(3)/2
y_sign = 1
condition1 = True
condition2 = True

while condition1:	#level1: first pos. y, then neg. y
	condition1 = (y>=0)
	while condition2:#level 2 counting y
		condition2 = False
		while wire_condition(x,y): #level 3 counting x
			condition2 = True
			x += 1
		x=0
		y+=(1*y_sign)

	y_sign = -1
	y = y_sign
	condition2 = True
#endregion
#os.system("pause")
"""
s = 0
i = 1
while i <= n:
    s = s + i
    i = i + 1

print "Die Summe lautet: ", s 
"""
