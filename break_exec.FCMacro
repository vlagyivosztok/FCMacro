from PyQt5.QtCore import Qt	 		
from PyQt5.QtWidgets import QProgressDialog

dialog =QProgressDialog()
dialog.setMinimum(0)
dialog.setLabelText("text")
dialog.setMaximum(0)
dialog.setWindowTitle("title")
dialog.setCancelButton(None)
dialog.setModal(False)
dialog.show()
