from PySide import QtGui, QtCore

class MyButtons(QtGui.QDialog):
	def __init__(self):
		super(MyButtons, self).__init__()
		self.initUI()
	def initUI(self):
		self.retStatus = 0
		option1Button = QtGui.QPushButton("Option 1")
		option1Button.clicked.connect(self.onOption1)
		option2Button = QtGui.QPushButton("Option 2")
		option2Button.clicked.connect(self.onOption2)
		option3Button = QtGui.QPushButton("Option 3")
		option3Button.clicked.connect(self.onOption3)
		option4Button = QtGui.QPushButton("Option 4")
		option4Button.clicked.connect(self.onOption4)
		option5Button = QtGui.QPushButton("Option 5")
		option5Button.clicked.connect(self.onOption5)
		
		buttonBox = QtGui.QDialogButtonBox(QtCore.Qt.Vertical)
		buttonBox.addButton(option1Button, QtGui.QDialogButtonBox.ActionRole)
		buttonBox.addButton(option2Button, QtGui.QDialogButtonBox.ActionRole)
		buttonBox.addButton(option3Button, QtGui.QDialogButtonBox.ActionRole)
		buttonBox.addButton(option4Button, QtGui.QDialogButtonBox.ActionRole)
		buttonBox.addButton(option5Button, QtGui.QDialogButtonBox.ActionRole)

		mainLayout = QtGui.QVBoxLayout()
		mainLayout.addWidget(buttonBox)
		self.setLayout(mainLayout)
		self.setGeometry(250,250,0,50)
		self.setWindowTitle("Pick a button")
		self.setWindowFlags(QtCore.Qt.WindowStaysOnTopHint)

	def onOption1(self):
		self.retStatus = 1
		self.close()
	def onOption2(self):
		self.retStatus = 2
		self.close()
	def onOption3(self):
		self.retStatus = 3
		self.close()
	def onOption4(self):
		self.retStatus = 4
		self.close()
	def onOption5(self):
		self.retStatus = 5
		self.close()

def routine1():
	print('routine1')
def routine2():
	print('routine2')
def routine3():
	print('routine3')
def routine4():
	print('routine4')
def routine5():
	print('routine5')

form = MyButtons()
form.exec()

if form.retStatus == 1:
	routine1()
elif form.retStatus == 2:
	routine2()
elif form.retStatus == 3:
	routine3()
elif form.retStatus == 4:
	routine4()
elif form.retStatus == 5:
	routine5()
else:
	print('no option')
