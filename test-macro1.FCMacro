import FreeCAD as App
g_UserMacroDir = (App.getUserMacroDir()).replace('\\','/')
g_wg_dir = g_UserMacroDir+"wg"

from pyquaternion import Quaternion
from pyquaternion.quaternion import np
from math import sqrt
from copy import deepcopy	#copy, 
import Draft
from PySide import QtGui #QWidget
from PySide import QtUiTools #QUiLoader
from PySide import QtCore #QFile, Q

""" 
Quaternion, matrix transzformacios gyakorlat.
2. resz
Test tetszoleges pozicioban, tetszoleges vektor (pontokkal)
vektorral parhuzamos vektor az origobol

mindket vektor normalt kiirasa
egyenlonek kell lenniuk


 """

#reply = QtGui.QMessageBox.critical(App, 'WINDING GEOM', 'Geometry will be calculated and generated...\nPlease wait!')
class Progress(QtGui.QWidget):
    def __init__(self):
       #rint('dbg','BackToMain init')
        super(Progress, self).__init__()
        self.loader = QtUiTools.QUiLoader()
        self.file = QtCore.QFile(g_wg_dir+"/Progress.ui")
        self.file.open(QtCore.QFile.ReadOnly)
        self.Widget = self.loader.load(self.file)
        self.file.close()
        #self.obj_MainWidget = None

My_Progress = Progress()
My_Progress.show()



raise Exception ('end')


def quat_rot(quat):		#pyquaternion.quaternion.Quaternion
	#rint(type(quat))
	if type(quat) == Quaternion:
		return_tuple = (round(quat[1],6),round(quat[2],6),round(quat[3],6),round(quat[0],6))
		return return_tuple
	else:
		return None

def def_quaternion(v1_, v2_, quat = False):
	#Quaternion v1 es v2 kozott, Tuple-t ad vissza FreeCAD formatumban
	#rint(type(v1),v1, type(v2),v2)

	v1 = copy(v1_)
	v2 = copy(v2_)
	#rint(id(v1),id(v1_), id(v2), id(v2_))

	v1.normalize(), v2.normalize()
	#rint(v1,v1_,v2,v2_)

	if(abs(v1.dot(v2)-1) < 0.0001):
			#parhuzamos, irany marad
		#rint('azonos')
		return_tuple = (0.0,0.0,0.0,1.0)
		return return_tuple

	elif(abs(v1.dot(v2)+1) < 0.0001):
		#rint('ellentetes')
		new_q = Quaternion(axis=[0, 1, 0], degrees=180) # (pyquaternion)
		#rint(new_q)
		return_tuple = (round(new_q[1],6),round(new_q[2],6),round(new_q[3],6),round(new_q[0],6))
		return return_tuple
	else: #altalanos helyzetu vektorok	

		##rint(v1,v2)
		v = v1+v2
		##rint(v)
		v.normalize()
		##rint(v)
		x_vect = v1.cross(v2)
		q_w = sqrt((pow(v1.Length,2)) * (pow(v2.Length,2))) + v1.dot(v2)
		new_q = Quaternion(q_w, x_vect[0], x_vect[1], x_vect[2])
		#rint((new_q.inverse).rotation_matrix)                
		if quat:
			return new_q
		else:
			return_tuple = (round(new_q[1],6),round(new_q[2],6),round(new_q[3],6),round(new_q[0],6))
			return return_tuple


# bazis koord rdsz
Test1= App.ActiveDocument.addObject('PartDesign::Body','test')
Gui.ActiveDocument.getObject(Test1.Origin.Name).Visibility = True
for item in Test1.Origin.OutList:
		if (item.Role).find('Z_Plane') >= 0:
			Gui.ActiveDocument.getObject(item.Name).Visibility = False

#az eltolt, elforgatott kr
Test2= App.ActiveDocument.addObject('PartDesign::Body','test')
Gui.ActiveDocument.getObject(Test2.Origin.Name).Visibility = True
for item in Test2.Origin.OutList:
		if (item.Role).find('Plane') >= 0:
			Gui.ActiveDocument.getObject(item.Name).Visibility = False

Test2.Placement.Base.x = 25
Test2.Placement.Base.y = 35
Test2.Placement.Base.z = 40

quat1 = Quaternion(axis=[2, 1, 4], degrees=33) 
Test2.Placement.Rotation = quat_rot(quat1)

#ket pont (vektor) a kr-ben
#newObject('PartDesign::Point','DatumPoint')

pt11 = App.ActiveDocument.getObject(Test2.Name).newObject('PartDesign::Point','DatumPoint')
pt21 = App.ActiveDocument.getObject(Test2.Name).newObject('PartDesign::Point','DatumPoint')

pt21.Placement.Base.x = 3
pt21.Placement.Base.y = 4
pt21.Placement.Base.z = 5


vekt1 = pt11.getGlobalPlacement().Base
vekt2 = pt21.getGlobalPlacement().Base

vekt_sub = vekt2.sub(vekt1)

#rint(vekt_sub.Length)

quat2 = def_quaternion(App.Vector(0,0,1),vekt_sub, True)
mx2 = quat2.rotation_matrix

print(type(mx2),mx2)

#pontok a Test1-be
pt1 = App.ActiveDocument.getObject(Test1.Name).newObject('PartDesign::Point','DatumPoint')
pt2 = App.ActiveDocument.getObject(Test1.Name).newObject('PartDesign::Point','DatumPoint')

vekt11 = App.Vector(0,0,5)

vekt21 = App.Vector(mx2.dot(vekt11))

vekt21.Length = vekt_sub.Length

pt2.Placement.Base = vekt21


#rint(vekt21, vekt_sub)
raise Exception('Tmp End')

#rint(vekt2.sub(vekt1).normalize(),pt2.Placement.Base.normalize())



ln = App.ActiveDocument.getObject('Test.Name').newObject('PartDesign::Line','DatumLine')

ln 

ln1 = Draft.makeLine(App.Vector(0,0,0),App.Vector(0,0,5))

vec1 = App.Vector(0,0,1)

mtx1 = quat1.rotation_matrix

vec1_rot = App.Vector(mtx1.dot(vec1))

ln1.Placement.Rotation = quat_rot(quat1)	#def_quaternion(vec1,vec1_rot)




Test= App.ActiveDocument.addObject('PartDesign::Body','test')


Gui.ActiveDocument.getObject(Test.Origin.Name).Visibility = True

Test.Placement.Rotation = quat_rot(quat1)
Gui.ActiveDocument.getObject(Test.Origin.Name).Visibility = True
for item in Test.Origin.OutList:
		if (item.Role).find('Plane') >= 0:
			Gui.ActiveDocument.getObject(item.Name).Visibility = False

ln1 = Draft.makeLine(App.Vector(0,0,0),App.Vector(5,1,5))

mtx1 = quat1.rotation_matrix

vec1 = App.Vector(1,0,0)
#rint(vec1)
vec1_rot = App.Vector(mtx1.dot(vec1))
#rint(vec1_rot)

ln_rot = def_quaternion(vec1,vec1_rot)

ln1.Placement.Rotation = ln_rot


#x = np.array( (2, 3, 5) )
#y = np.matrix( ((1,2), (5, -1)) )
#rint(quat1.rotation_matrix * x)
""" matrix([[17,  1],
        [28,  1]]) """


#test1 = App.ActiveDocument.getObject('test')
#test1.Placement.Rotation = 

#rint(quat_rot(quat1))
#rint(quat1.rotation_matrix)
