"""
pontokon kereztul ket gorbe
tovuknel 1 nagy korlap, ket kis kor, huzalok, szigetelessel
"""
#import Draft

##try:
lista = []

for obj in App.ActiveDocument.Objects:
	#print(obj.Name)
	lista.append(obj.Name)
if len(lista):
	for Name in lista:
		pass
		#print(Name)
		App.ActiveDocument.removeObject(Name)	


else:
	print('letrehoz')
	test = 'test1'
	pontok1 = (('pont1',10,5,0),('pont2',10,5,5),('pont3',10,5,10),('pont4',10,5,15),('pont5',10,5,20),('pont6',10,0,40),('pont7',10,30,60),('pont8',10,5,80))
	pontok2 = (('pont11',30,5,0),('pont12',30,5,5),('pont13',30,5,10),('pont14',30,5,15),('pont15',30,5,20),('pont16',30,0,40),('pont17',30,30,60),('pont18',30,5,80))
	Vectors1 = []
	Vectors2 = []
	Pontok1 =[]
	Pontok2 =[]
	Test= App.ActiveDocument.addObject('PartDesign::Body',test)
	for pont in pontok1:
		#print(pont)
		Pontok1.append(Test.newObject('PartDesign::Point',pont[0]))
		Test.getObject(pont[0]).Placement.Base.x = pont[1]
		Test.getObject(pont[0]).Placement.Base.y = pont[2]
		Test.getObject(pont[0]).Placement.Base.z = pont[3]
	for pont in pontok2:
		#print(pont)
		Pontok2.append(Test.newObject('PartDesign::Point',pont[0]))
		Test.getObject(pont[0]).Placement.Base.x = pont[1]
		Test.getObject(pont[0]).Placement.Base.y = pont[2]
		Test.getObject(pont[0]).Placement.Base.z = pont[3]
	#print(Pontok)
	for Pont in Pontok1:
		Vectors1.append(App.Vector(Pont.Placement.Base.x,Pont.Placement.Base.y,Pont.Placement.Base.z))
	for Pont in Pontok2:
		Vectors2.append(App.Vector(Pont.Placement.Base.x,Pont.Placement.Base.y,Pont.Placement.Base.z))
	#print(Vectors)
	spline1 = Draft.makeBSpline(Vectors1,closed=False,face=False,support=None)
	spline2 = Draft.makeBSpline(Vectors2,closed=False,face=False,support=None)
	pl1=App.Placement()
	pl2=App.Placement()
	pl1.Rotation.Q=(0,0,0,1)	# Z irany
	pl1.Base=FreeCAD.Vector(Vectors1[0])
	circle1 = Draft.makeCircle(radius=0.3,placement=pl1,face=False,support=None)
	circle11 = Draft.makeCircle(radius=0.29,placement=pl1,face=False,support=None)
	pl2.Base=FreeCAD.Vector(Vectors2[0])
	circle2 = Draft.makeCircle(radius=0.3,placement=pl2,face=False,support=None)
	circle21 = Draft.makeCircle(radius=0.29,placement=pl2,face=False,support=None)
	circle_base = Draft.makeCircle(radius=100,placement=pl1,face=False,support=None)

	


	test = 'test2'
	Test= App.ActiveDocument.addObject('PartDesign::Body',test)
	Test.addObject(spline1)
	Test.addObject(spline2)	
	Test.addObject(circle1)
	Test.addObject(circle2)
	Test.addObject(circle11)
	Test.addObject(circle21)
	Test.addObject(circle_base)

	pad1 = App.ActiveDocument.getObject(test).newObject("PartDesign::Pad","Pad01")
	App.ActiveDocument.getObject("Pad01").Profile =  App.ActiveDocument.getObject(circle_base.Name)
	App.ActiveDocument.getObject("Pad01").Length = 2
	App.ActiveDocument.getObject("Pad01").Reversed = 1

	Test.newObject("PartDesign::AdditivePipe","AdditivePipe1")
	App.ActiveDocument.getObject("AdditivePipe1").Profile = App.ActiveDocument.getObject(circle1.Name)
	App.ActiveDocument.getObject("AdditivePipe1").Spine = App.ActiveDocument.getObject(spline1.Name),['Edge1']

	Test.newObject("PartDesign::AdditivePipe","AdditivePipe2")
	App.ActiveDocument.getObject("AdditivePipe2").Profile = App.ActiveDocument.getObject(circle2.Name)
	App.ActiveDocument.getObject("AdditivePipe2").Spine = App.ActiveDocument.getObject(spline1.Name),['Edge1']

	App.ActiveDocument.recompute()

	Test.newObject("PartDesign::SubtractivePipe","SubtractivePipe11")
	App.ActiveDocument.getObject("SubtractivePipe11").Profile = App.ActiveDocument.getObject(circle11.Name)
	App.ActiveDocument.getObject("SubtractivePipe11").Spine = App.ActiveDocument.getObject(spline1.Name),['Edge1']

	Test.newObject("PartDesign::SubtractivePipe","SubtractivePipe21")
	App.ActiveDocument.getObject("SubtractivePipe21").Profile = App.ActiveDocument.getObject(circle21.Name)
	App.ActiveDocument.getObject("SubtractivePipe21").Spine = App.ActiveDocument.getObject(spline2.Name),['Edge1']
	
	App.ActiveDocument.recompute()	

	Gui.ActiveDocument.getObject("AdditivePipe1").Visibility=False
	Gui.ActiveDocument.getObject("AdditivePipe2").Visibility=False

	test = 'test3'
	Test= App.ActiveDocument.addObject('PartDesign::Body',test)

	spline11 = Draft.makeBSpline(Vectors1,closed=False,face=False,support=None)
	pl=App.Placement()
	pl.Rotation.Q=(0,0,0,1)	# Z irany
	pl.Base=FreeCAD.Vector(Vectors1[0])
	circle3 = Draft.makeCircle(radius=0.29,placement=pl,face=False,support=None)

	spline21 = Draft.makeBSpline(Vectors2,closed=False,face=False,support=None)
	pl=App.Placement()
	pl.Rotation.Q=(0,0,0,1)	# Z irany
	pl.Base=FreeCAD.Vector(Vectors2[0])
	circle31 = Draft.makeCircle(radius=0.29,placement=pl,face=False,support=None)

	Test.addObject(spline11)
	Test.addObject(circle3)
	Test.addObject(spline21)
	Test.addObject(circle31)

	Test.newObject("PartDesign::AdditivePipe","AdditivePipe3")
	App.ActiveDocument.getObject("AdditivePipe3").Profile = App.ActiveDocument.getObject(circle3.Name)
	App.ActiveDocument.getObject("AdditivePipe3").Spine = App.ActiveDocument.getObject(spline11.Name),['Edge1']

	Test.newObject("PartDesign::AdditivePipe","AdditivePipe31")
	App.ActiveDocument.getObject("AdditivePipe31").Profile = App.ActiveDocument.getObject(circle31.Name)
	App.ActiveDocument.getObject("AdditivePipe31").Spine = App.ActiveDocument.getObject(spline21.Name),['Edge1']

	App.ActiveDocument.recompute()
	
#except:
	#print('error')

#App.activeDocument().recompute()
