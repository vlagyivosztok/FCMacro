from pyquaternion import Quaternion
from math import sqrt
""" 
pontokra illesztett bodyk, adott vektorukkal abszolut origo fele forditva.
 """

def def_quaternion(v1, v2):
	""" Get rotation Quaternion between 2 vectors """
	v1.normalize(), v2.normalize()

	if(abs(v1.dot(v2)-1) < 0.0001):
    		#parhuzamos, irany marad
		print('azonos')
		return_tuple = (0.0,0.0,0.0,1.0)
		return return_tuple

	elif(abs(v1.dot(v2)+1) < 0.0001):
		print('ellentetes')
		new_q = Quaternion(axis=[0, 1, 0], degrees=180) # (pyquaternion)
		print(new_q)
		return_tuple = (round(new_q[1],6),round(new_q[2],6),round(new_q[3],6),round(new_q[0],6))
		return return_tuple

	else: #altalanos helyzetu vektorok	

		#print(v1,v2)
		v = v1+v2
		#print(v)
		v.normalize()
		#print(v)
		x_vect = v1.cross(v2)
		q_w = sqrt((pow(v1.Length,2)) * (pow(v2.Length,2))) + v1.dot(v2)
		new_q = Quaternion(q_w, x_vect[0], x_vect[1], x_vect[2])                
		return_tuple = (round(new_q[1],6),round(new_q[2],6),round(new_q[3],6),round(new_q[0],6))
		return return_tuple

lista = []

for obj in App.ActiveDocument.Objects:
	#print(obj.Name)
	lista.append(obj.Name)
if len(lista):
	for Name in lista:
		pass
		#print(Name)
		App.ActiveDocument.removeObject(Name)

else:
	pontok1 = [(30,5,0),(60,15,0),(90,35,0),(120,55,0),(150,35,0),(180,25,0),(210,15,0),(240,5,0)]
	Vectors1 = []
	#Vectors2 = []
	Pontok1 =[]
	#Pontok2 =[]
	testek1 = []

	test = 'test1'

	Test= App.ActiveDocument.addObject('PartDesign::Body',test)
	Gui.ActiveDocument.getObject(Test.Origin.Name).Visibility = True
	for pont in pontok1:
		#print(pont)
		akt_pont = Test.newObject('PartDesign::Point','pont')
		Pontok1.append(akt_pont)
		Test.getObject(akt_pont.Name).Placement.Base.x = pont[0]
		Test.getObject(akt_pont.Name).Placement.Base.y = pont[1]
		Test.getObject(akt_pont.Name).Placement.Base.z = pont[2]

	for Pont in Pontok1:
		Vectors1.append(App.Vector(Pont.Placement.Base.x,Pont.Placement.Base.y,Pont.Placement.Base.z))	

	for vector in Vectors1:
		Test= App.ActiveDocument.addObject('PartDesign::Body',test)
		testek1.append(Test)
		Test.Placement.Base.x = vector.x
		Test.Placement.Base.y = vector.y
		Test.Placement.Base.z = vector.z

		#App.ActiveDocument.getObject(Test.Name).Placement.Rotation = rot
		Test.Placement.Rotation = def_quaternion(App.Vector(0,1,1),-vector)
		Gui.ActiveDocument.getObject(Test.Origin.Name).Visibility = True
		for item in Test.Origin.OutList:
    			if (item.Role).find('Plane') >= 0:
    				Gui.ActiveDocument.getObject(item.Name).Visibility = False


	""" 
	minden pontba egy body-t
	a body 0,1,0 vektorat a 0,0,0 iranyba allitani
	body: obj.Origin.OutList[]

	>>> Gui.ActiveDocument.getObject(orig1.OutList[0].Name).Visibility = False
	>>> orig1.OutList
	>>> orig1.OutList[3].Role
	'XY_Plane', 'X_Axis'
	 """

""" v1 = App.Vector(2,0,0)
v2 = App.Vector(0,0,-10)

Test= App.ActiveDocument.addObject('PartDesign::Body','test')
Gui.ActiveDocument.getObject(Test.Origin.Name).Visibility = True

pont1 = Test.newObject('PartDesign::Point','pont')
pont1.Placement.Base.x = v1.x
pont1.Placement.Base.y = v1.y
pont1.Placement.Base.z = v1.z

Test2= App.ActiveDocument.addObject('PartDesign::Body','test')
Gui.ActiveDocument.getObject(Test2.Origin.Name).Visibility = True

rot = def_quaternion(v1, v2)
print(rot)
App.ActiveDocument.getObject(Test2.Name).Placement.Rotation = rot """
