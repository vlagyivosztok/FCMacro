g_UserMacroDir = (App.getUserMacroDir()).replace('\\','/')
g_WG_dir = g_UserMacroDir+"wg"

import os

try:
    from wg.interfaces import MainWidget, BackToMain, CheckResults
    from wg.creategeom import CreateGeom
except:
    os.system(g_WG_dir+'\import-error.vbs')
    raise Exception("Quit winding-geom.FCMacro")

MyMainWidget = MainWidget()

MyBackToMain = BackToMain()
MyMainWidget.obj_BackToMain =  MyBackToMain
MyBackToMain.obj_MainWidget = MyMainWidget

MyCheckResults = CheckResults()
MyMainWidget.obj_CheckResults = MyCheckResults
MyCheckResults.obj_MainWidget = MyMainWidget

MyCheckResults.GeomInput = MyMainWidget.GeomInput

MyCreateGeom = CreateGeom()
MyCreateGeom.obj_MainWidget = MyMainWidget
MyMainWidget.obj_CreateGeom = MyCreateGeom


MyMainWidget.Show_()
